FME workspace lod1_join_footprint_cityjson.fmw

Parameters:
- SourceDataset_GEODATABASE_FILE_4 = E:\QL_2022\UBDC_data_catalogue_3d_city_DONE\building_products\lod1_3d_building_model_part2\building_model_lod1_part2_v2.gdb   # File Geodatabase
- DestDataset_GEODATABASE_FILE_2 = E:\QL_2022\UBDC_data_catalogue_3d_city_DONE\building_products\lod1_3d_building_model_part2\building_model_lod1_part2_v2.gdb   # File Geodatabase
- DestDataset_GEODATABASE_FILE = E:\QL_2022\UBDC_data_catalogue_3d_city_DONE\building_products\lod1_3d_building_model_part2\building_model_lod1_part2_v2.gdb   # File Geodatabase
- DestDataset_CITYJSON = E:\QL_2022\UBDC_data_catalogue_3d_city_DONE\building_products\lod1_3d_building_model_part2_json   # Destination CityJSON File
- SourceDataset_GEODATABASE_FILE_7 = E:\QL_2022\UBDC_data_catalogue_3d_city_DONE\building_products\building_footprints_part2\building_footprints_part2.gdb   # File Geodatabase
- FEATURE_TYPES =
- SourceDataset_GEODATABASE_FILE = E:\QL_2022\UBDC_data_catalogue_3d_city_DONE\building_products\lod1_3d_building_model_part2\building_model_lod1_part2.gdb   # File Geodatabase
- FEATURE_TYPES_2 =

Readers:
- GEODATABASE_FILE_3: GEODATABASE_FILE from $(SourceDataset_GEODATABASE_FILE_4)
- GEODATABASE_FILE_6: GEODATABASE_FILE from $(SourceDataset_GEODATABASE_FILE_7)
- GEODATABASE_FILE_1: GEODATABASE_FILE from $(SourceDataset_GEODATABASE_FILE)

Writers:
- GEODATABASE_FILE_4: GEODATABASE_FILE to $(DestDataset_GEODATABASE_FILE)
- GEODATABASE_FILE_5: GEODATABASE_FILE to $(DestDataset_GEODATABASE_FILE_2)
- CITYJSON_1: CITYJSON to $(DestDataset_CITYJSON) in EPSG:27700

NS46NE (reader GEODATABASE_FILE_1)
    attributes: OID integer, Name char(255)
    -> AttributeManager_2
AttributeManager_2
    ATTR_TABLE:
      RENAME_SET_VALUE Name > Mesh_Name
      SET_TO U_ID = @ReplaceString(@Value(Mesh_Name),.obj,,caseSensitive=TRUE)
      REMOVE fme_feature_type
    -> FeatureJoiner [LEFT]
NS46NE (reader GEODATABASE_FILE_6)
    attributes: OBJECTID integer, Shape_Length double, Shape_Area double, tile_name char(20), U_ID char(30), MIN double, MAX double, RANGE double, MEAN double, STD double, SUM double, MEDIAN double, PCT90 double, Ground_Z double, Remark char(255)
    -> AttributeManager
AttributeManager
    ATTR_TABLE:
      REMOVE OBJECTID
      REMOVE MIN
      REMOVE MAX
      REMOVE RANGE
      RENAME_SET_VALUE MEAN > Building_Height
      REMOVE STD
      REMOVE SUM
      REMOVE MEDIAN
      REMOVE PCT90
      RENAME_SET_VALUE Shape_Length > Footprint_Length
      RENAME_SET_VALUE Shape_Area > Footprint_Area
      REMOVE Remark
      REMOVE fme_feature_type
    -> FeatureJoiner [RIGHT]
FeatureJoiner
    ATTR_CONFLICT_RES = Prefer Right
    GEOMETRY_HANDLING = Prefer Left
    GROUP_BY = fme_feature_type
    JOIN_KEYS = U_ID U_ID AUTO
    JOIN_MODE = Left
    JOINED -> FeatureClass1 (writer GEODATABASE_FILE_4)
    JOINED -> AttributeManager_3
FeatureClass1 (writer GEODATABASE_FILE_4)
    attributes: OID integer, Mesh_Name char(255), U_ID char(200), tile_name char(20), Building_Height double, Ground_Z double, Footprint_Length double, Footprint_Area double
AttributeManager_3
    ATTR_TABLE:
      REMOVE OID
      SET_TO fid = @Value(U_ID)
      SET_TO lod = 1
    USER_EXPOSED_ATTRIBUTES = fid
    -> Building (writer CITYJSON_1)
Building (writer CITYJSON_1)
    attributes: Mesh_Name string, U_ID string, Building_Height real64, Ground_Z real64, Footprint_Length real64, Footprint_Area real64, fid string, lod string, tile_name string
