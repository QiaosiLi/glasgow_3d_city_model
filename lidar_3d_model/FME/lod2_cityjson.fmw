FME workspace lod2_cityjson.fmw

Parameters:
- SourceDataset_GEODATABASE_FILE = E:\QL_2022\UBDC_data_catalogue_3d_city_DONE\building_products\lod1_3d_building_model\building_model_lod1.gdb   # File Geodatabase
- DestDataset_CITYJSON = E:\QL_2022\UBDC_data_catalogue_3d_city_DONE\building_products\lod2_3d_building_model_json   # Destination CityJSON File
- DestDataset_CITYJSON_5 = E:\QL_2022\UBDC_data_catalogue_3d_city_DONE\building_products\lod2_3d_building_model_json   # Destination CityJSON File
- SourceDataset_GEODATABASE_FILE_5 = E:\QL_2022\UBDC_data_catalogue_3d_city_DONE\building_products\lod2_3d_building_model\building_model_lod2.gdb   # File Geodatabase
- SourceDataset_GEODATABASE_FILE_4 = E:\QL_2022\UBDC_data_catalogue_3d_city_DONE\building_products\lod2_3d_building_model\building_model_lod2.gdb   # File Geodatabase

Readers:
- GEODATABASE_FILE_1: GEODATABASE_FILE from $(SourceDataset_GEODATABASE_FILE)
- GEODATABASE_FILE_2: GEODATABASE_FILE from $(SourceDataset_GEODATABASE_FILE_5)
- GEODATABASE_FILE_3: GEODATABASE_FILE from $(SourceDataset_GEODATABASE_FILE_4)

Writers:
- CITYJSON_1: CITYJSON to $(DestDataset_CITYJSON) in EPSG:27700
- CITYJSON_3: CITYJSON to $(DestDataset_CITYJSON_5) in EPSG:27700

NS56NE_V2 (reader GEODATABASE_FILE_3)
    attributes: OBJECTID_1 integer, Name char(255), U_ID char(255), fp_Area double, fp_Len double, OBJECTID integer, MIN double, MAX double, RANGE double, MEAN double, STD double, SUM double, MEDIAN double, PCT90 double, U_ID_1 char(80), Ground_Z double, tile_name char(254)
    -> AttributeValidator
NS56SE_V2 (reader GEODATABASE_FILE_2) [off]
    attributes: OBJECTID_1 integer, Name char(255), U_ID char(255), Fp_Len double, Fp_Area double, OBJECTID integer, MIN double, MAX double, RANGE double, MEAN double, STD double, SUM double, MEDIAN double, PCT90 double, U_ID_1 char(80), Shape_Leng double, Ground_Z double, tile_name char(254)
    -> AttributeValidator
NS66NW_V2 (reader GEODATABASE_FILE_2) [off]
    attributes: OBJECTID_1 integer, Name char(255), U_ID char(255), Fp_Len double, Fp_Area double, OBJECTID integer, MIN double, MAX double, RANGE double, MEAN double, STD double, SUM double, MEDIAN double, PCT90 double, U_ID_1 char(80), Shape_Leng double, Ground_Z double, tile_name char(254)
    -> AttributeValidator
NS66SW_V2 (reader GEODATABASE_FILE_2) [off]
    attributes: OBJECTID_1 integer, Name char(255), U_ID char(255), Fp_Len double, Fp_Area double, OBJECTID integer, MIN double, MAX double, RANGE double, MEAN double, STD double, SUM double, MEDIAN double, PCT90 double, U_ID_1 char(80), Shape_Leng double, Ground_Z double, tile_name char(254)
    -> AttributeValidator
AttributeValidator
    TABLE = MIN;ATTRIBUTE_NOT_NULL;<Unused>
    PASSED -> AttributeManager
    FAILED -> AttributeManager_2
AttributeManager
    ATTR_TABLE:
      RENAME_SET_VALUE Name > Mesh_name
      SET_TO fid = @Value(U_ID)
      SET_TO lod = 2
      REMOVE OBJECTID_1
      REMOVE SUM
      REMOVE tile_name
      RENAME_SET_VALUE fp_Area > Footprint_Area
      RENAME_SET_VALUE fp_Len > Footprint_Length
      REMOVE OBJECTID
      REMOVE RANGE
      REMOVE STD
      REMOVE MEDIAN
      REMOVE U_ID_1
      REMOVE Fp_Len
      REMOVE Fp_Area
      REMOVE Shape_Leng
    -> Building (writer CITYJSON_1)
Building (writer CITYJSON_1)
    attributes: Mesh_name string, U_ID string, Ground_Z real64, fid string, lod string, MIN real64, MAX real64, MEAN real64, PCT90 real64, Footprint_Area real64, Footprint_Length real64
AttributeManager_2
    ATTR_TABLE:
      RENAME_SET_VALUE Name > Mesh_name
      REMOVE Ground_Z
      SET_TO fid = @Value(U_ID)
      SET_TO lod = 2
      REMOVE OBJECTID_1
      REMOVE MIN
      REMOVE MAX
      REMOVE MEAN
      REMOVE SUM
      REMOVE PCT90
      REMOVE tile_name
      REMOVE _fme_validation_message
      REMOVE _fme_validation_message_list{}
      REMOVE fp_Area
      REMOVE fp_Len
      REMOVE OBJECTID
      REMOVE RANGE
      REMOVE STD
      REMOVE MEDIAN
      REMOVE U_ID_1
      REMOVE Fp_Len
      REMOVE Fp_Area
      REMOVE Shape_Leng
    -> Building (writer CITYJSON_3)
Building (writer CITYJSON_3)
    attributes: Mesh_name string, U_ID string, fid string, lod string
